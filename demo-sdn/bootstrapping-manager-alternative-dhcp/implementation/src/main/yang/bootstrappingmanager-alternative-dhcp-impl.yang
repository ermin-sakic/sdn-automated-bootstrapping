module bootstrappingmanager-alternative-dhcp-impl {
    yang-version 1;
    namespace "urn:eu:virtuwind:bootstrappingmanager:alternative:dhcp:impl";
    prefix "bootstrappingmanager-alternative-dhcp-impl";

    import config { prefix config; revision-date 2013-04-05; }
    import opendaylight-md-sal-binding { prefix mdsal; revision-date 2013-10-28; }
    import netty { prefix netty; }
    import ietf-inet-types { prefix inet; }
    import opendaylight-entity-ownership-service { prefix eos; revision-date 2015-08-10; }

    description
        "This module contains the base YANG definitions for bootstrappingmanager-alternative-dhcp-impl.";

    revision "2016-12-10" {
        description
            "Initial revision.";
    }


    identity dhcp-lease-manager {
            base "config:service-type";
            config:java-class "org.apache.directory.server.dhcp.service.manager.LeaseManager";
        }

        identity example-lease-manager {
            base config:module-type;
            config:provided-service dhcp-lease-manager;
        }

        augment "/config:modules/config:module/config:configuration" {
            case example-lease-manager {
                when "/config:modules/config:module/config:type = 'example-lease-manager'";

                leaf ip {
                    type string;
                    description "Ip to lease to every client";
                }
            }
        }

        typedef message-type {
            type enumeration {
                enum "DHCPOFFER" {
                    value 2;
                    description "DHCP Offer";
                }
                enum "DHCPACK" {
                    value 5;
                    description "DHCP Acknowledge";
                 }
                 enum "DHCPNAK" {
                     value 6;
                     description "DHCP Not Acknowledge";
                 }
                 enum "ALL" {
                     value 9;
                     description "all DHCP messages";
                 }
             }
         }

        grouping dhcp-range {
                 leaf dhcp-addr-range-begin {
                     type string;
                 }

                 leaf dhcp-addr-range-end {
                     type string;
                 }
        }

        identity dhcp {
            base config:module-type;
            config:java-name-prefix Dhcp;
        }

        augment "/config:modules/config:module/config:configuration" {
            case dhcp {
                when "/config:modules/config:module/config:type = 'dhcp'";

            //wires in the data-broker service
            container data-broker {
                uses config:service-ref {
                    refine type {
                        mandatory true;
                        config:required-identity mdsal:binding-async-data-broker;
                    }
                }
            }

            container entity-ownership-service {
                uses config:service-ref {
                    refine type {
                        mandatory true;
                        config:required-identity eos:entity-ownership-service;
                    }
                }
            }

            container rpc-registry {
                uses config:service-ref {
                    refine type {
                        mandatory true;
                        config:required-identity mdsal:binding-rpc-registry;
                    }
                }
            }

            container worker-thread-group {
                uses config:service-ref {
                    refine type {
                        config:required-identity netty:netty-threadgroup;
                    }
                }
            }

            leaf port {
                type inet:port-number;
                description "port to bind the DHCP server to";
                default 67;
            }

            leaf-list network-interface {
                description "network interfaces upon the dhcp server should listen to";
                type string;
             }

            list default-option {
                description "options which will be included in the chosen outcoming DHCP message";
                key "id scope";
                leaf id {
                    type uint16;
                }
                leaf value {
                    type string;
                }
                leaf scope {
                    type message-type;
                }
             }

            container lease-manager {
                uses config:service-ref {
                    refine type {
                        config:required-identity dhcp-lease-manager;
                    }
                }
            }

            // used by the DHCP server
            container dhcp-server-config {

                list dhcp-ranges {
                    uses dhcp-range;
                }

                list bind-dhcp-interface {
                     description "Interface name for listening";
                     leaf interface-name {
                         type string;
                     }
                }

                leaf dhcp-config-mode {
                    description "Select how to provide initial DHCP config to the server xml or via REST";
                    type string;
                    default "auto";
                    //other option is viaREST
                }

                 leaf expected-discovery-period {
                    type uint32;
                    default 1010; // in miliseconds
                }

                leaf dhcp-duplication-protection {
                    description "Enable/Disable additional logic that drops sequential multiple discovery and requests";
                    type boolean;
                    default false;
                }

            }

        }
    }

}
