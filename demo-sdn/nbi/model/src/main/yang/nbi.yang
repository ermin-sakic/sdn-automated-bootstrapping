module nbi {
	yang-version 1;
	namespace "urn:eu:virtuwind:nbi:model";
	prefix "nbi-model";

	import opendaylight-inventory {prefix inv; revision-date 2013-08-19;}
	import yang-ext {prefix ext; revision-date 2013-07-09;}
	import ietf-yang-types { prefix yang; revision-date 2010-09-24; }
	import ietf-inet-types { prefix inet; }

	description "Application Request Model";

	revision "2016-07-04" {
		description "Initial version.";
	}

    grouping CommunicationServiceRequest {
        leaf communicationServiceId {
            type int32;

            mandatory false;
        }

            leaf source-node-id {
                type string;
                config true;
                mandatory true;
                description "Uniquely identifies a Connectivity Matrix Association <Source Node, List<Destination Node>> map.";
            }

            leaf destination-node-id {
                    type string;
                    config true;
                    mandatory true;
             }

                leaf sustainableRate {
                    type int32;
                    mandatory false;
                }

                leaf maximumBurst {
                    type int32;

                    mandatory false;
                }

                leaf maxPacketSize {
                    type int32;

                    mandatory false;
                }

                leaf maximumLatency {
                    type int32;

                    mandatory false;
                }

                leaf reliability {
                    type Reliability;

                    mandatory false;
                }
    }

    typedef Reliability {
		type enumeration {
			enum "SEAMLESS";
			enum "NONE";
		}
    }

	typedef CsAddCommServResult {
		type enumeration {
			enum "SUCCESS";
			enum "DENIED";
			enum "FAILURE";
		}
	}

	typedef CsDelCommServResult {
		type enumeration {
			enum "SUCCESS";
			enum "DENIED";
			enum "FAILURE";
		}
	}

	typedef CsGetCommServResult {
		type enumeration {
			enum "SUCCESS";
			enum "DENIED";
			enum "FAILURE";
		}
	}

	rpc cs-add-comm-serv {
		input {
			uses CommunicationServiceRequest {
			}
		}

		output {
			leaf result {
				type CsAddCommServResult;
			}

            leaf reason {
				type string;
			}
		}
	}

	rpc cs-del-comm-serv {
		input {
			uses CommunicationServiceRequest {
				refine communicationServiceId {
					mandatory true;
				}
			}
		}

		output {
			leaf result {
				type CsDelCommServResult;
			}
                        leaf reason {
				type string;
			}
		}
	}

	rpc cs-get-comm-serv {
		input {
			uses CommunicationServiceRequest {
				refine communicationServiceId {
					mandatory true;
				}
			}
		}

		output {
			uses CommunicationServiceRequest;

			leaf result {
				type CsGetCommServResult;
			}
		}
	}
}
